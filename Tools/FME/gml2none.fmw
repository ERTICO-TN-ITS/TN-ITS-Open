FME workspace gml2none.fmw

Parameters:
- SourceDataset_GML =
- SourceDataset_GML_3 =

Readers:
- GML_1: GML from $(SourceDataset_GML)
- GML_2: GML from $(SourceDataset_GML_3)

Note: RoadFeature: ExampleDataset_FeatureCollection [GML]
RoadFeature (reader GML_1)
    attributes: validFrom xml_date, validTo xml_date, beginLifespanVersion xml_datetime, endLifespanVersion xml_datetime, updateInfo.UpdateInfo.type xml_char(6), source.owns xml_boolean, source.nilReason xml_buffer, source.gml_remoteSchema xml_buffer, source.xlink_href xml_buffer, source.xlink_role xml_buffer, source.xlink_title xml_buffer, type.owns xml_boolean, type.nilReason xml_buffer, type.gml_remoteSchema xml_buffer, type.xlink_href xml_buffer, type.xlink_role xml_buffer, type.xlink_title xml_buffer, properties{}.GenericRoadFeatureProperty.type.owns xml_boolean, properties{}.GenericRoadFeatureProperty.type.nilReason xml_buffer, properties{}.GenericRoadFeatureProperty.type.gml_remoteSchema xml_buffer, properties{}.GenericRoadFeatureProperty.type.xlink_href xml_buffer, properties{}.GenericRoadFeatureProperty.type.xlink_role xml_buffer, properties{}.GenericRoadFeatureProperty.type.xlink_title xml_buffer, properties{}.GenericRoadFeatureProperty.value{} xml_xml, properties{}.GenericRoadFeatureProperty.valueReference{}.owns xml_boolean, properties{}.GenericRoadFeatureProperty.valueReference{}.nilReason xml_buffer, properties{}.GenericRoadFeatureProperty.valueReference{}.gml_remoteSchema xml_buffer, properties{}.GenericRoadFeatureProperty.valueReference{}.xlink_href xml_buffer, properties{}.GenericRoadFeatureProperty.valueReference{}.xlink_role xml_buffer, properties{}.GenericRoadFeatureProperty.valueReference{}.xlink_title xml_buffer,
      properties{}.RoadSignProperty.gddCode.owns xml_boolean, properties{}.RoadSignProperty.gddCode.nilReason xml_buffer, properties{}.RoadSignProperty.gddCode.gml_remoteSchema xml_buffer, properties{}.RoadSignProperty.gddCode.xlink_href xml_buffer, properties{}.RoadSignProperty.gddCode.xlink_role xml_buffer, properties{}.RoadSignProperty.gddCode.xlink_title xml_buffer, properties{}.RoadSignProperty.content{}.RoadSignContent.value xml_real64, properties{}.RoadSignProperty.content{}.RoadSignContent.value.uom xml_buffer, properties{}.RoadSignProperty.content{}.RoadSignContent.text xml_buffer, properties{}.RoadSignProperty.content{}.RoadSignContent.natureOfDistance.owns xml_boolean, properties{}.RoadSignProperty.content{}.RoadSignContent.natureOfDistance.nilReason xml_buffer, properties{}.RoadSignProperty.content{}.RoadSignContent.natureOfDistance.gml_remoteSchema xml_buffer, properties{}.RoadSignProperty.content{}.RoadSignContent.natureOfDistance.xlink_href xml_buffer, properties{}.RoadSignProperty.content{}.RoadSignContent.natureOfDistance.xlink_role xml_buffer, properties{}.RoadSignProperty.content{}.RoadSignContent.natureOfDistance.xlink_title xml_buffer, id.RoadFeatureId.providerId xml_buffer, id.RoadFeatureId.id xml_buffer, condition.AreaCondition.negate xml_boolean, condition.AreaCondition.areaType.owns xml_boolean, condition.AreaCondition.areaType.nilReason xml_buffer, condition.AreaCondition.areaType.gml_remoteSchema xml_buffer, condition.AreaCondition.areaType.xlink_href xml_buffer, condition.AreaCondition.areaType.xlink_role xml_buffer, condition.AreaCondition.areaType.xlink_title xml_buffer, condition.ConditionSet.negate xml_boolean, condition.ConditionSet.operator xml_char(3), condition.ConditionSet.conditions{}.AreaCondition xml_xml, condition.ConditionSet.conditions{}.ConditionSet xml_xml, condition.ConditionSet.conditions{}.LaneCondition xml_xml, condition.ConditionSet.conditions{}.RoadCategoryCondition xml_xml,
      condition.ConditionSet.conditions{}.TimeCondition xml_xml, condition.ConditionSet.conditions{}.VehicleCondition xml_xml, condition.ConditionSet.conditions{}.WeatherCondition xml_xml, condition.LaneCondition.negate xml_boolean, condition.LaneCondition.startLane xml_int64, condition.LaneCondition.laneExtension xml_int64, condition.RoadCategoryCondition.negate xml_boolean, condition.RoadCategoryCondition.roadCategory.owns xml_boolean, condition.RoadCategoryCondition.roadCategory.nilReason xml_buffer, condition.RoadCategoryCondition.roadCategory.gml_remoteSchema xml_buffer, condition.RoadCategoryCondition.roadCategory.xlink_href xml_buffer, condition.RoadCategoryCondition.roadCategory.xlink_role xml_buffer, condition.RoadCategoryCondition.roadCategory.xlink_title xml_buffer, condition.TimeCondition.negate xml_boolean, condition.TimeCondition.validityPeriod.Validity.validityTimeSpecification.OverallPeriod.overallStartTime xml_datetime, condition.TimeCondition.validityPeriod.Validity.validityTimeSpecification.OverallPeriod.overallEndTime xml_datetime, condition.TimeCondition.validityPeriod.Validity.validityTimeSpecification.OverallPeriod.validPeriod{}.Period.startOfPeriod xml_datetime, condition.TimeCondition.validityPeriod.Validity.validityTimeSpecification.OverallPeriod.validPeriod{}.Period.endOfPeriod xml_datetime, condition.TimeCondition.validityPeriod.Validity.validityTimeSpecification.OverallPeriod.validPeriod{}.Period.periodName xml_buffer, condition.TimeCondition.validityPeriod.Validity.validityTimeSpecification.OverallPeriod.validPeriod{}.Period.recurringDayWeekMonthPeriod{}.DayWeekMonth.applicableDay{} xml_char(9), condition.TimeCondition.validityPeriod.Validity.validityTimeSpecification.OverallPeriod.validPeriod{}.Period.recurringDayWeekMonthPeriod{}.DayWeekMonth.applicableWeek{} xml_char(10), condition.TimeCondition.validityPeriod.Validity.validityTimeSpecification.OverallPeriod.validPeriod{}.Period.recurringDayWeekMonthPeriod{}.DayWeekMonth.applicableMonth{} xml_char(9), condition.TimeCondition.validityPeriod.Validity.validityTimeSpecification.OverallPeriod.validPeriod{}.Period.recurringFuzzyTimePeriod{}.FuzzyTimePeriod.beginOrDuration.owns xml_boolean, condition.TimeCondition.validityPeriod.Validity.validityTimeSpecification.OverallPeriod.validPeriod{}.Period.recurringFuzzyTimePeriod{}.FuzzyTimePeriod.beginOrDuration.nilReason xml_buffer, condition.TimeCondition.validityPeriod.Validity.validityTimeSpecification.OverallPeriod.validPeriod{}.Period.recurringFuzzyTimePeriod{}.FuzzyTimePeriod.beginOrDuration.gml_remoteSchema xml_buffer, condition.TimeCondition.validityPeriod.Validity.validityTimeSpecification.OverallPeriod.validPeriod{}.Period.recurringFuzzyTimePeriod{}.FuzzyTimePeriod.beginOrDuration.xlink_href xml_buffer, condition.TimeCondition.validityPeriod.Validity.validityTimeSpecification.OverallPeriod.validPeriod{}.Period.recurringFuzzyTimePeriod{}.FuzzyTimePeriod.beginOrDuration.xlink_role xml_buffer, condition.TimeCondition.validityPeriod.Validity.validityTimeSpecification.OverallPeriod.validPeriod{}.Period.recurringFuzzyTimePeriod{}.FuzzyTimePeriod.beginOrDuration.xlink_title xml_buffer, condition.TimeCondition.validityPeriod.Validity.validityTimeSpecification.OverallPeriod.validPeriod{}.Period.recurringFuzzyTimePeriod{}.FuzzyTimePeriod.endOrDuration.owns xml_boolean, condition.TimeCondition.validityPeriod.Validity.validityTimeSpecification.OverallPeriod.validPeriod{}.Period.recurringFuzzyTimePeriod{}.FuzzyTimePeriod.endOrDuration.nilReason xml_buffer,
      condition.TimeCondition.validityPeriod.Validity.validityTimeSpecification.OverallPeriod.validPeriod{}.Period.recurringFuzzyTimePeriod{}.FuzzyTimePeriod.endOrDuration.gml_remoteSchema xml_buffer, condition.TimeCondition.validityPeriod.Validity.validityTimeSpecification.OverallPeriod.validPeriod{}.Period.recurringFuzzyTimePeriod{}.FuzzyTimePeriod.endOrDuration.xlink_href xml_buffer, condition.TimeCondition.validityPeriod.Validity.validityTimeSpecification.OverallPeriod.validPeriod{}.Period.recurringFuzzyTimePeriod{}.FuzzyTimePeriod.endOrDuration.xlink_role xml_buffer, condition.TimeCondition.validityPeriod.Validity.validityTimeSpecification.OverallPeriod.validPeriod{}.Period.recurringFuzzyTimePeriod{}.FuzzyTimePeriod.endOrDuration.xlink_title xml_buffer, condition.TimeCondition.validityPeriod.Validity.validityTimeSpecification.OverallPeriod.validPeriod{}.Period.recurringTimePeriodOfDay{}.TimePeriodOfDay.startTimeOfPeriod xml_time, condition.TimeCondition.validityPeriod.Validity.validityTimeSpecification.OverallPeriod.validPeriod{}.Period.recurringTimePeriodOfDay{}.TimePeriodOfDay.endTimeOfPeriod xml_time, condition.TimeCondition.validityPeriod.Validity.validityTimeSpecification.OverallPeriod.validPeriod{}.Period.recurringSpecialDay{}.PublicHoliday.intersectWithApplicableDays xml_boolean, condition.TimeCondition.validityPeriod.Validity.validityTimeSpecification.OverallPeriod.validPeriod{}.Period.recurringSpecialDay{}.PublicHoliday.specialDayType.owns xml_boolean, condition.TimeCondition.validityPeriod.Validity.validityTimeSpecification.OverallPeriod.validPeriod{}.Period.recurringSpecialDay{}.PublicHoliday.specialDayType.nilReason xml_buffer, condition.TimeCondition.validityPeriod.Validity.validityTimeSpecification.OverallPeriod.validPeriod{}.Period.recurringSpecialDay{}.PublicHoliday.specialDayType.gml_remoteSchema xml_buffer, condition.TimeCondition.validityPeriod.Validity.validityTimeSpecification.OverallPeriod.validPeriod{}.Period.recurringSpecialDay{}.PublicHoliday.specialDayType.xlink_href xml_buffer, condition.TimeCondition.validityPeriod.Validity.validityTimeSpecification.OverallPeriod.validPeriod{}.Period.recurringSpecialDay{}.PublicHoliday.specialDayType.xlink_role xml_buffer, condition.TimeCondition.validityPeriod.Validity.validityTimeSpecification.OverallPeriod.validPeriod{}.Period.recurringSpecialDay{}.PublicHoliday.specialDayType.xlink_title xml_buffer, condition.TimeCondition.validityPeriod.Validity.validityTimeSpecification.OverallPeriod.validPeriod{}.Period.recurringSpecialDay{}.PublicHoliday.publicEvent xml_buffer, condition.TimeCondition.validityPeriod.Validity.validityTimeSpecification.OverallPeriod.validPeriod{}.Period.recurringSpecialDay{}.PublicHoliday.publicHolidayName xml_buffer, condition.TimeCondition.validityPeriod.Validity.validityTimeSpecification.OverallPeriod.validPeriod{}.Period.recurringSpecialDay{}.SpecialDay.intersectWithApplicableDays xml_boolean, condition.TimeCondition.validityPeriod.Validity.validityTimeSpecification.OverallPeriod.validPeriod{}.Period.recurringSpecialDay{}.SpecialDay.specialDayType.owns xml_boolean, condition.TimeCondition.validityPeriod.Validity.validityTimeSpecification.OverallPeriod.validPeriod{}.Period.recurringSpecialDay{}.SpecialDay.specialDayType.nilReason xml_buffer, condition.TimeCondition.validityPeriod.Validity.validityTimeSpecification.OverallPeriod.validPeriod{}.Period.recurringSpecialDay{}.SpecialDay.specialDayType.gml_remoteSchema xml_buffer, condition.TimeCondition.validityPeriod.Validity.validityTimeSpecification.OverallPeriod.validPeriod{}.Period.recurringSpecialDay{}.SpecialDay.specialDayType.xlink_href xml_buffer, condition.TimeCondition.validityPeriod.Validity.validityTimeSpecification.OverallPeriod.validPeriod{}.Period.recurringSpecialDay{}.SpecialDay.specialDayType.xlink_role xml_buffer, condition.TimeCondition.validityPeriod.Validity.validityTimeSpecification.OverallPeriod.validPeriod{}.Period.recurringSpecialDay{}.SpecialDay.specialDayType.xlink_title xml_buffer, condition.TimeCondition.validityPeriod.Validity.validityTimeSpecification.OverallPeriod.validPeriod{}.Period.recurringSpecialDay{}.SpecialDay.publicEvent xml_buffer, condition.TimeCondition.validityPeriod.Validity.validityTimeSpecification.OverallPeriod.exceptionPeriod{}.Period.startOfPeriod xml_datetime, condition.TimeCondition.validityPeriod.Validity.validityTimeSpecification.OverallPeriod.exceptionPeriod{}.Period.endOfPeriod xml_datetime, condition.TimeCondition.validityPeriod.Validity.validityTimeSpecification.OverallPeriod.exceptionPeriod{}.Period.periodName xml_buffer, condition.TimeCondition.validityPeriod.Validity.validityTimeSpecification.OverallPeriod.exceptionPeriod{}.Period.recurringDayWeekMonthPeriod{}.DayWeekMonth.applicableDay{} xml_char(9), condition.TimeCondition.validityPeriod.Validity.validityTimeSpecification.OverallPeriod.exceptionPeriod{}.Period.recurringDayWeekMonthPeriod{}.DayWeekMonth.applicableWeek{} xml_char(10), condition.TimeCondition.validityPeriod.Validity.validityTimeSpecification.OverallPeriod.exceptionPeriod{}.Period.recurringDayWeekMonthPeriod{}.DayWeekMonth.applicableMonth{} xml_char(9), condition.TimeCondition.validityPeriod.Validity.validityTimeSpecification.OverallPeriod.exceptionPeriod{}.Period.recurringFuzzyTimePeriod{}.FuzzyTimePeriod.beginOrDuration.owns xml_boolean,
      condition.TimeCondition.validityPeriod.Validity.validityTimeSpecification.OverallPeriod.exceptionPeriod{}.Period.recurringFuzzyTimePeriod{}.FuzzyTimePeriod.beginOrDuration.nilReason xml_buffer, condition.TimeCondition.validityPeriod.Validity.validityTimeSpecification.OverallPeriod.exceptionPeriod{}.Period.recurringFuzzyTimePeriod{}.FuzzyTimePeriod.beginOrDuration.gml_remoteSchema xml_buffer, condition.TimeCondition.validityPeriod.Validity.validityTimeSpecification.OverallPeriod.exceptionPeriod{}.Period.recurringFuzzyTimePeriod{}.FuzzyTimePeriod.beginOrDuration.xlink_href xml_buffer, condition.TimeCondition.validityPeriod.Validity.validityTimeSpecification.OverallPeriod.exceptionPeriod{}.Period.recurringFuzzyTimePeriod{}.FuzzyTimePeriod.beginOrDuration.xlink_role xml_buffer, condition.TimeCondition.validityPeriod.Validity.validityTimeSpecification.OverallPeriod.exceptionPeriod{}.Period.recurringFuzzyTimePeriod{}.FuzzyTimePeriod.beginOrDuration.xlink_title xml_buffer, condition.TimeCondition.validityPeriod.Validity.validityTimeSpecification.OverallPeriod.exceptionPeriod{}.Period.recurringFuzzyTimePeriod{}.FuzzyTimePeriod.endOrDuration.owns xml_boolean, condition.TimeCondition.validityPeriod.Validity.validityTimeSpecification.OverallPeriod.exceptionPeriod{}.Period.recurringFuzzyTimePeriod{}.FuzzyTimePeriod.endOrDuration.nilReason xml_buffer, condition.TimeCondition.validityPeriod.Validity.validityTimeSpecification.OverallPeriod.exceptionPeriod{}.Period.recurringFuzzyTimePeriod{}.FuzzyTimePeriod.endOrDuration.gml_remoteSchema xml_buffer, condition.TimeCondition.validityPeriod.Validity.validityTimeSpecification.OverallPeriod.exceptionPeriod{}.Period.recurringFuzzyTimePeriod{}.FuzzyTimePeriod.endOrDuration.xlink_href xml_buffer, condition.TimeCondition.validityPeriod.Validity.validityTimeSpecification.OverallPeriod.exceptionPeriod{}.Period.recurringFuzzyTimePeriod{}.FuzzyTimePeriod.endOrDuration.xlink_role xml_buffer, condition.TimeCondition.validityPeriod.Validity.validityTimeSpecification.OverallPeriod.exceptionPeriod{}.Period.recurringFuzzyTimePeriod{}.FuzzyTimePeriod.endOrDuration.xlink_title xml_buffer, condition.TimeCondition.validityPeriod.Validity.validityTimeSpecification.OverallPeriod.exceptionPeriod{}.Period.recurringTimePeriodOfDay{}.TimePeriodOfDay.startTimeOfPeriod xml_time, condition.TimeCondition.validityPeriod.Validity.validityTimeSpecification.OverallPeriod.exceptionPeriod{}.Period.recurringTimePeriodOfDay{}.TimePeriodOfDay.endTimeOfPeriod xml_time, condition.TimeCondition.validityPeriod.Validity.validityTimeSpecification.OverallPeriod.exceptionPeriod{}.Period.recurringSpecialDay{}.PublicHoliday.intersectWithApplicableDays xml_boolean, condition.TimeCondition.validityPeriod.Validity.validityTimeSpecification.OverallPeriod.exceptionPeriod{}.Period.recurringSpecialDay{}.PublicHoliday.specialDayType.owns xml_boolean, condition.TimeCondition.validityPeriod.Validity.validityTimeSpecification.OverallPeriod.exceptionPeriod{}.Period.recurringSpecialDay{}.PublicHoliday.specialDayType.nilReason xml_buffer, condition.TimeCondition.validityPeriod.Validity.validityTimeSpecification.OverallPeriod.exceptionPeriod{}.Period.recurringSpecialDay{}.PublicHoliday.specialDayType.gml_remoteSchema xml_buffer, condition.TimeCondition.validityPeriod.Validity.validityTimeSpecification.OverallPeriod.exceptionPeriod{}.Period.recurringSpecialDay{}.PublicHoliday.specialDayType.xlink_href xml_buffer, condition.TimeCondition.validityPeriod.Validity.validityTimeSpecification.OverallPeriod.exceptionPeriod{}.Period.recurringSpecialDay{}.PublicHoliday.specialDayType.xlink_role xml_buffer, condition.TimeCondition.validityPeriod.Validity.validityTimeSpecification.OverallPeriod.exceptionPeriod{}.Period.recurringSpecialDay{}.PublicHoliday.specialDayType.xlink_title xml_buffer, condition.TimeCondition.validityPeriod.Validity.validityTimeSpecification.OverallPeriod.exceptionPeriod{}.Period.recurringSpecialDay{}.PublicHoliday.publicEvent xml_buffer, condition.TimeCondition.validityPeriod.Validity.validityTimeSpecification.OverallPeriod.exceptionPeriod{}.Period.recurringSpecialDay{}.PublicHoliday.publicHolidayName xml_buffer, condition.TimeCondition.validityPeriod.Validity.validityTimeSpecification.OverallPeriod.exceptionPeriod{}.Period.recurringSpecialDay{}.SpecialDay.intersectWithApplicableDays xml_boolean, condition.TimeCondition.validityPeriod.Validity.validityTimeSpecification.OverallPeriod.exceptionPeriod{}.Period.recurringSpecialDay{}.SpecialDay.specialDayType.owns xml_boolean, condition.TimeCondition.validityPeriod.Validity.validityTimeSpecification.OverallPeriod.exceptionPeriod{}.Period.recurringSpecialDay{}.SpecialDay.specialDayType.nilReason xml_buffer, condition.TimeCondition.validityPeriod.Validity.validityTimeSpecification.OverallPeriod.exceptionPeriod{}.Period.recurringSpecialDay{}.SpecialDay.specialDayType.gml_remoteSchema xml_buffer, condition.TimeCondition.validityPeriod.Validity.validityTimeSpecification.OverallPeriod.exceptionPeriod{}.Period.recurringSpecialDay{}.SpecialDay.specialDayType.xlink_href xml_buffer, condition.TimeCondition.validityPeriod.Validity.validityTimeSpecification.OverallPeriod.exceptionPeriod{}.Period.recurringSpecialDay{}.SpecialDay.specialDayType.xlink_role xml_buffer, condition.TimeCondition.validityPeriod.Validity.validityTimeSpecification.OverallPeriod.exceptionPeriod{}.Period.recurringSpecialDay{}.SpecialDay.specialDayType.xlink_title xml_buffer, condition.TimeCondition.validityPeriod.Validity.validityTimeSpecification.OverallPeriod.exceptionPeriod{}.Period.recurringSpecialDay{}.SpecialDay.publicEvent xml_buffer,
      condition.VehicleCondition.negate xml_boolean, condition.VehicleCondition.vehicleCharacteristics.VehicleCharacteristics.fuelType{}.owns xml_boolean, condition.VehicleCondition.vehicleCharacteristics.VehicleCharacteristics.fuelType{}.nilReason xml_buffer, condition.VehicleCondition.vehicleCharacteristics.VehicleCharacteristics.fuelType{}.gml_remoteSchema xml_buffer, condition.VehicleCondition.vehicleCharacteristics.VehicleCharacteristics.fuelType{}.xlink_href xml_buffer, condition.VehicleCondition.vehicleCharacteristics.VehicleCharacteristics.fuelType{}.xlink_role xml_buffer, condition.VehicleCondition.vehicleCharacteristics.VehicleCharacteristics.fuelType{}.xlink_title xml_buffer, condition.VehicleCondition.vehicleCharacteristics.VehicleCharacteristics.loadType.owns xml_boolean, condition.VehicleCondition.vehicleCharacteristics.VehicleCharacteristics.loadType.nilReason xml_buffer, condition.VehicleCondition.vehicleCharacteristics.VehicleCharacteristics.loadType.gml_remoteSchema xml_buffer, condition.VehicleCondition.vehicleCharacteristics.VehicleCharacteristics.loadType.xlink_href xml_buffer, condition.VehicleCondition.vehicleCharacteristics.VehicleCharacteristics.loadType.xlink_role xml_buffer, condition.VehicleCondition.vehicleCharacteristics.VehicleCharacteristics.loadType.xlink_title xml_buffer, condition.VehicleCondition.vehicleCharacteristics.VehicleCharacteristics.vehicleEquipment.owns xml_boolean, condition.VehicleCondition.vehicleCharacteristics.VehicleCharacteristics.vehicleEquipment.nilReason xml_buffer, condition.VehicleCondition.vehicleCharacteristics.VehicleCharacteristics.vehicleEquipment.gml_remoteSchema xml_buffer, condition.VehicleCondition.vehicleCharacteristics.VehicleCharacteristics.vehicleEquipment.xlink_href xml_buffer, condition.VehicleCondition.vehicleCharacteristics.VehicleCharacteristics.vehicleEquipment.xlink_role xml_buffer, condition.VehicleCondition.vehicleCharacteristics.VehicleCharacteristics.vehicleEquipment.xlink_title xml_buffer, condition.VehicleCondition.vehicleCharacteristics.VehicleCharacteristics.vehicleType{}.owns xml_boolean, condition.VehicleCondition.vehicleCharacteristics.VehicleCharacteristics.vehicleType{}.nilReason xml_buffer, condition.VehicleCondition.vehicleCharacteristics.VehicleCharacteristics.vehicleType{}.gml_remoteSchema xml_buffer, condition.VehicleCondition.vehicleCharacteristics.VehicleCharacteristics.vehicleType{}.xlink_href xml_buffer, condition.VehicleCondition.vehicleCharacteristics.VehicleCharacteristics.vehicleType{}.xlink_role xml_buffer, condition.VehicleCondition.vehicleCharacteristics.VehicleCharacteristics.vehicleType{}.xlink_title xml_buffer, condition.VehicleCondition.vehicleCharacteristics.VehicleCharacteristics.vehicleUsage.owns xml_boolean, condition.VehicleCondition.vehicleCharacteristics.VehicleCharacteristics.vehicleUsage.nilReason xml_buffer, condition.VehicleCondition.vehicleCharacteristics.VehicleCharacteristics.vehicleUsage.gml_remoteSchema xml_buffer, condition.VehicleCondition.vehicleCharacteristics.VehicleCharacteristics.vehicleUsage.xlink_href xml_buffer, condition.VehicleCondition.vehicleCharacteristics.VehicleCharacteristics.vehicleUsage.xlink_role xml_buffer,
      condition.VehicleCondition.vehicleCharacteristics.VehicleCharacteristics.vehicleUsage.xlink_title xml_buffer, condition.VehicleCondition.vehicleCharacteristics.VehicleCharacteristics.yearOfFirstRegistration xml_int64, condition.VehicleCondition.vehicleCharacteristics.VehicleCharacteristics.heightCharacteristic{}.HeightCharacteristic.comparisonOperator xml_char(20), condition.VehicleCondition.vehicleCharacteristics.VehicleCharacteristics.heightCharacteristic{}.HeightCharacteristic.vehicleHeight xml_real64, condition.VehicleCondition.vehicleCharacteristics.VehicleCharacteristics.heightCharacteristic{}.HeightCharacteristic.vehicleHeight.uom xml_buffer, condition.VehicleCondition.vehicleCharacteristics.VehicleCharacteristics.widthCharacteristic{}.WidthCharacteristic.comparisonOperator xml_char(20), condition.VehicleCondition.vehicleCharacteristics.VehicleCharacteristics.widthCharacteristic{}.WidthCharacteristic.vehicleWidth xml_real64, condition.VehicleCondition.vehicleCharacteristics.VehicleCharacteristics.widthCharacteristic{}.WidthCharacteristic.vehicleWidth.uom xml_buffer, condition.VehicleCondition.vehicleCharacteristics.VehicleCharacteristics.heaviestAxleWeightCharacteristic{}.HeaviestAxleWeightCharacteristic.comparisonOperator xml_char(20), condition.VehicleCondition.vehicleCharacteristics.VehicleCharacteristics.heaviestAxleWeightCharacteristic{}.HeaviestAxleWeightCharacteristic.heaviestAxleWeight xml_real64, condition.VehicleCondition.vehicleCharacteristics.VehicleCharacteristics.heaviestAxleWeightCharacteristic{}.HeaviestAxleWeightCharacteristic.heaviestAxleWeight.uom xml_buffer, condition.VehicleCondition.vehicleCharacteristics.VehicleCharacteristics.grossWeightCharacteristic{}.GrossWeightCharacteristic.comparisonOperator xml_char(20), condition.VehicleCondition.vehicleCharacteristics.VehicleCharacteristics.grossWeightCharacteristic{}.GrossWeightCharacteristic.grossVehicleWeight xml_real64, condition.VehicleCondition.vehicleCharacteristics.VehicleCharacteristics.grossWeightCharacteristic{}.GrossWeightCharacteristic.grossVehicleWeight.uom xml_buffer, condition.VehicleCondition.vehicleCharacteristics.VehicleCharacteristics.grossWeightCharacteristic{}.GrossWeightCharacteristic.typeOfWeight.owns xml_boolean, condition.VehicleCondition.vehicleCharacteristics.VehicleCharacteristics.grossWeightCharacteristic{}.GrossWeightCharacteristic.typeOfWeight.nilReason xml_buffer, condition.VehicleCondition.vehicleCharacteristics.VehicleCharacteristics.grossWeightCharacteristic{}.GrossWeightCharacteristic.typeOfWeight.gml_remoteSchema xml_buffer, condition.VehicleCondition.vehicleCharacteristics.VehicleCharacteristics.grossWeightCharacteristic{}.GrossWeightCharacteristic.typeOfWeight.xlink_href xml_buffer, condition.VehicleCondition.vehicleCharacteristics.VehicleCharacteristics.grossWeightCharacteristic{}.GrossWeightCharacteristic.typeOfWeight.xlink_role xml_buffer, condition.VehicleCondition.vehicleCharacteristics.VehicleCharacteristics.grossWeightCharacteristic{}.GrossWeightCharacteristic.typeOfWeight.xlink_title xml_buffer, condition.VehicleCondition.vehicleCharacteristics.VehicleCharacteristics.numberOfAxlesCharacteristic{}.NumberOfAxlesCharacteristic.comparisonOperator xml_char(20), condition.VehicleCondition.vehicleCharacteristics.VehicleCharacteristics.numberOfAxlesCharacteristic{}.NumberOfAxlesCharacteristic.numberOfAxles xml_int64, condition.VehicleCondition.vehicleCharacteristics.VehicleCharacteristics.emissions{}.Emissions.emissionClassificationEuro.owns xml_boolean, condition.VehicleCondition.vehicleCharacteristics.VehicleCharacteristics.emissions{}.Emissions.emissionClassificationEuro.nilReason xml_buffer, condition.VehicleCondition.vehicleCharacteristics.VehicleCharacteristics.emissions{}.Emissions.emissionClassificationEuro.gml_remoteSchema xml_buffer, condition.VehicleCondition.vehicleCharacteristics.VehicleCharacteristics.emissions{}.Emissions.emissionClassificationEuro.xlink_href xml_buffer, condition.VehicleCondition.vehicleCharacteristics.VehicleCharacteristics.emissions{}.Emissions.emissionClassificationEuro.xlink_role xml_buffer, condition.VehicleCondition.vehicleCharacteristics.VehicleCharacteristics.emissions{}.Emissions.emissionClassificationEuro.xlink_title xml_buffer, condition.VehicleCondition.vehicleCharacteristics.VehicleCharacteristics.emissions{}.Emissions.emissionClassificationOther{} xml_buffer, condition.VehicleCondition.vehicleCharacteristics.VehicleCharacteristics.emissions{}.Emissions.emissionLevel.owns xml_boolean,
      condition.VehicleCondition.vehicleCharacteristics.VehicleCharacteristics.emissions{}.Emissions.emissionLevel.nilReason xml_buffer, condition.VehicleCondition.vehicleCharacteristics.VehicleCharacteristics.emissions{}.Emissions.emissionLevel.gml_remoteSchema xml_buffer, condition.VehicleCondition.vehicleCharacteristics.VehicleCharacteristics.emissions{}.Emissions.emissionLevel.xlink_href xml_buffer, condition.VehicleCondition.vehicleCharacteristics.VehicleCharacteristics.emissions{}.Emissions.emissionLevel.xlink_role xml_buffer, condition.VehicleCondition.vehicleCharacteristics.VehicleCharacteristics.emissions{}.Emissions.emissionLevel.xlink_title xml_buffer, condition.VehicleCondition.vehicleCharacteristics.VehicleCharacteristics.lengthCharacteristic{}.LengthCharacteristic.comparisonOperator xml_char(20), condition.VehicleCondition.vehicleCharacteristics.VehicleCharacteristics.lengthCharacteristic{}.LengthCharacteristic.vehicleLength xml_real64, condition.VehicleCondition.vehicleCharacteristics.VehicleCharacteristics.lengthCharacteristic{}.LengthCharacteristic.vehicleLength.uom xml_buffer, condition.WeatherCondition.negate xml_boolean, condition.WeatherCondition.weatherType.owns xml_boolean, condition.WeatherCondition.weatherType.nilReason xml_buffer, condition.WeatherCondition.weatherType.gml_remoteSchema xml_buffer, condition.WeatherCondition.weatherType.xlink_href xml_buffer, condition.WeatherCondition.weatherType.xlink_role xml_buffer, condition.WeatherCondition.weatherType.xlink_title xml_buffer, locationReference{} xml_xml, locationReference{}.GeometryLocationReference.encodedGeometry.LineString.posList xml_char(501), locationReference{}.GeometryLocationReference.encodedGeometry.LineString.srsDimension xml_decimal(2,0), locationReference{}.GeometryLocationReference.encodedGeometry.LineString.srsName xml_char(10), locationReference{}.GeometryLocationReference.encodedGeometry.Point.pos xml_char(38), locationReference{}.GeometryLocationReference.encodedGeometry.Point.srsDimension xml_decimal(2,0), locationReference{}.GeometryLocationReference.encodedGeometry.Point.srsName xml_char(10), locationReference{}.OpenLRLocationReference.binaryLocationReference.BinaryLocationReference.base64String xml_char(25), locationReference{}.OpenLRLocationReference.binaryLocationReference.BinaryLocationReference.openLRBinaryVersion xml_char(1), locationReference{}.OpenLRLocationReference.binaryLocationReference.BinaryLocationReference.openLRBinaryVersion.href xml_char(61), properties{}.GenericRoadFeatureProperty.value{}.measure xml_decimal(2,0), properties{}.GenericRoadFeatureProperty.value{}.measure.uom xml_char(4)
    -> ListSearcher [off]
    -> RoadFeature_FC
RoadFeature_FC: Inspector
Note: RoadFeature: Example_RoadDataSet [GML]
RoadFeature (reader GML_2)
    attributes: validFrom xml_date, validTo xml_date, beginLifespanVersion xml_datetime, endLifespanVersion xml_datetime, updateInfo.UpdateInfo.type xml_char(6), source.owns xml_boolean, source.nilReason xml_buffer, source.gml_remoteSchema xml_buffer, source.xlink_href xml_buffer, source.xlink_role xml_buffer, source.xlink_title xml_buffer, type.owns xml_boolean, type.nilReason xml_buffer, type.gml_remoteSchema xml_buffer, type.xlink_href xml_buffer, type.xlink_role xml_buffer, type.xlink_title xml_buffer, properties{}.GenericRoadFeatureProperty.type.owns xml_boolean, properties{}.GenericRoadFeatureProperty.type.nilReason xml_buffer, properties{}.GenericRoadFeatureProperty.type.gml_remoteSchema xml_buffer, properties{}.GenericRoadFeatureProperty.type.xlink_href xml_buffer, properties{}.GenericRoadFeatureProperty.type.xlink_role xml_buffer, properties{}.GenericRoadFeatureProperty.type.xlink_title xml_buffer, properties{}.GenericRoadFeatureProperty.value{} xml_xml, properties{}.GenericRoadFeatureProperty.valueReference{}.owns xml_boolean, properties{}.GenericRoadFeatureProperty.valueReference{}.nilReason xml_buffer, properties{}.GenericRoadFeatureProperty.valueReference{}.gml_remoteSchema xml_buffer, properties{}.GenericRoadFeatureProperty.valueReference{}.xlink_href xml_buffer, properties{}.GenericRoadFeatureProperty.valueReference{}.xlink_role xml_buffer, properties{}.GenericRoadFeatureProperty.valueReference{}.xlink_title xml_buffer,
      properties{}.RoadSignProperty.gddCode.owns xml_boolean, properties{}.RoadSignProperty.gddCode.nilReason xml_buffer, properties{}.RoadSignProperty.gddCode.gml_remoteSchema xml_buffer, properties{}.RoadSignProperty.gddCode.xlink_href xml_buffer, properties{}.RoadSignProperty.gddCode.xlink_role xml_buffer, properties{}.RoadSignProperty.gddCode.xlink_title xml_buffer, properties{}.RoadSignProperty.content{}.RoadSignContent.value xml_real64, properties{}.RoadSignProperty.content{}.RoadSignContent.value.uom xml_buffer, properties{}.RoadSignProperty.content{}.RoadSignContent.text xml_buffer, properties{}.RoadSignProperty.content{}.RoadSignContent.natureOfDistance.owns xml_boolean, properties{}.RoadSignProperty.content{}.RoadSignContent.natureOfDistance.nilReason xml_buffer, properties{}.RoadSignProperty.content{}.RoadSignContent.natureOfDistance.gml_remoteSchema xml_buffer, properties{}.RoadSignProperty.content{}.RoadSignContent.natureOfDistance.xlink_href xml_buffer, properties{}.RoadSignProperty.content{}.RoadSignContent.natureOfDistance.xlink_role xml_buffer, properties{}.RoadSignProperty.content{}.RoadSignContent.natureOfDistance.xlink_title xml_buffer, id.RoadFeatureId.providerId xml_buffer, id.RoadFeatureId.id xml_buffer, condition.AreaCondition.negate xml_boolean, condition.AreaCondition.areaType.owns xml_boolean, condition.AreaCondition.areaType.nilReason xml_buffer, condition.AreaCondition.areaType.gml_remoteSchema xml_buffer, condition.AreaCondition.areaType.xlink_href xml_buffer, condition.AreaCondition.areaType.xlink_role xml_buffer, condition.AreaCondition.areaType.xlink_title xml_buffer, condition.ConditionSet.negate xml_boolean, condition.ConditionSet.operator xml_char(3), condition.ConditionSet.conditions{}.AreaCondition xml_xml, condition.ConditionSet.conditions{}.ConditionSet xml_xml, condition.ConditionSet.conditions{}.LaneCondition xml_xml, condition.ConditionSet.conditions{}.RoadCategoryCondition xml_xml,
      condition.ConditionSet.conditions{}.TimeCondition xml_xml, condition.ConditionSet.conditions{}.VehicleCondition xml_xml, condition.ConditionSet.conditions{}.WeatherCondition xml_xml, condition.LaneCondition.negate xml_boolean, condition.LaneCondition.startLane xml_int64, condition.LaneCondition.laneExtension xml_int64, condition.RoadCategoryCondition.negate xml_boolean, condition.RoadCategoryCondition.roadCategory.owns xml_boolean, condition.RoadCategoryCondition.roadCategory.nilReason xml_buffer, condition.RoadCategoryCondition.roadCategory.gml_remoteSchema xml_buffer, condition.RoadCategoryCondition.roadCategory.xlink_href xml_buffer, condition.RoadCategoryCondition.roadCategory.xlink_role xml_buffer, condition.RoadCategoryCondition.roadCategory.xlink_title xml_buffer, condition.TimeCondition.negate xml_boolean, condition.TimeCondition.validityPeriod.Validity.validityTimeSpecification.OverallPeriod.overallStartTime xml_datetime, condition.TimeCondition.validityPeriod.Validity.validityTimeSpecification.OverallPeriod.overallEndTime xml_datetime, condition.TimeCondition.validityPeriod.Validity.validityTimeSpecification.OverallPeriod.validPeriod{}.Period.startOfPeriod xml_datetime, condition.TimeCondition.validityPeriod.Validity.validityTimeSpecification.OverallPeriod.validPeriod{}.Period.endOfPeriod xml_datetime, condition.TimeCondition.validityPeriod.Validity.validityTimeSpecification.OverallPeriod.validPeriod{}.Period.periodName xml_buffer, condition.TimeCondition.validityPeriod.Validity.validityTimeSpecification.OverallPeriod.validPeriod{}.Period.recurringDayWeekMonthPeriod{}.DayWeekMonth.applicableDay{} xml_char(9), condition.TimeCondition.validityPeriod.Validity.validityTimeSpecification.OverallPeriod.validPeriod{}.Period.recurringDayWeekMonthPeriod{}.DayWeekMonth.applicableWeek{} xml_char(10), condition.TimeCondition.validityPeriod.Validity.validityTimeSpecification.OverallPeriod.validPeriod{}.Period.recurringDayWeekMonthPeriod{}.DayWeekMonth.applicableMonth{} xml_char(9), condition.TimeCondition.validityPeriod.Validity.validityTimeSpecification.OverallPeriod.validPeriod{}.Period.recurringFuzzyTimePeriod{}.FuzzyTimePeriod.beginOrDuration.owns xml_boolean, condition.TimeCondition.validityPeriod.Validity.validityTimeSpecification.OverallPeriod.validPeriod{}.Period.recurringFuzzyTimePeriod{}.FuzzyTimePeriod.beginOrDuration.nilReason xml_buffer, condition.TimeCondition.validityPeriod.Validity.validityTimeSpecification.OverallPeriod.validPeriod{}.Period.recurringFuzzyTimePeriod{}.FuzzyTimePeriod.beginOrDuration.gml_remoteSchema xml_buffer, condition.TimeCondition.validityPeriod.Validity.validityTimeSpecification.OverallPeriod.validPeriod{}.Period.recurringFuzzyTimePeriod{}.FuzzyTimePeriod.beginOrDuration.xlink_href xml_buffer, condition.TimeCondition.validityPeriod.Validity.validityTimeSpecification.OverallPeriod.validPeriod{}.Period.recurringFuzzyTimePeriod{}.FuzzyTimePeriod.beginOrDuration.xlink_role xml_buffer, condition.TimeCondition.validityPeriod.Validity.validityTimeSpecification.OverallPeriod.validPeriod{}.Period.recurringFuzzyTimePeriod{}.FuzzyTimePeriod.beginOrDuration.xlink_title xml_buffer, condition.TimeCondition.validityPeriod.Validity.validityTimeSpecification.OverallPeriod.validPeriod{}.Period.recurringFuzzyTimePeriod{}.FuzzyTimePeriod.endOrDuration.owns xml_boolean, condition.TimeCondition.validityPeriod.Validity.validityTimeSpecification.OverallPeriod.validPeriod{}.Period.recurringFuzzyTimePeriod{}.FuzzyTimePeriod.endOrDuration.nilReason xml_buffer,
      condition.TimeCondition.validityPeriod.Validity.validityTimeSpecification.OverallPeriod.validPeriod{}.Period.recurringFuzzyTimePeriod{}.FuzzyTimePeriod.endOrDuration.gml_remoteSchema xml_buffer, condition.TimeCondition.validityPeriod.Validity.validityTimeSpecification.OverallPeriod.validPeriod{}.Period.recurringFuzzyTimePeriod{}.FuzzyTimePeriod.endOrDuration.xlink_href xml_buffer, condition.TimeCondition.validityPeriod.Validity.validityTimeSpecification.OverallPeriod.validPeriod{}.Period.recurringFuzzyTimePeriod{}.FuzzyTimePeriod.endOrDuration.xlink_role xml_buffer, condition.TimeCondition.validityPeriod.Validity.validityTimeSpecification.OverallPeriod.validPeriod{}.Period.recurringFuzzyTimePeriod{}.FuzzyTimePeriod.endOrDuration.xlink_title xml_buffer, condition.TimeCondition.validityPeriod.Validity.validityTimeSpecification.OverallPeriod.validPeriod{}.Period.recurringTimePeriodOfDay{}.TimePeriodOfDay.startTimeOfPeriod xml_time, condition.TimeCondition.validityPeriod.Validity.validityTimeSpecification.OverallPeriod.validPeriod{}.Period.recurringTimePeriodOfDay{}.TimePeriodOfDay.endTimeOfPeriod xml_time, condition.TimeCondition.validityPeriod.Validity.validityTimeSpecification.OverallPeriod.validPeriod{}.Period.recurringSpecialDay{}.PublicHoliday.intersectWithApplicableDays xml_boolean, condition.TimeCondition.validityPeriod.Validity.validityTimeSpecification.OverallPeriod.validPeriod{}.Period.recurringSpecialDay{}.PublicHoliday.specialDayType.owns xml_boolean, condition.TimeCondition.validityPeriod.Validity.validityTimeSpecification.OverallPeriod.validPeriod{}.Period.recurringSpecialDay{}.PublicHoliday.specialDayType.nilReason xml_buffer, condition.TimeCondition.validityPeriod.Validity.validityTimeSpecification.OverallPeriod.validPeriod{}.Period.recurringSpecialDay{}.PublicHoliday.specialDayType.gml_remoteSchema xml_buffer, condition.TimeCondition.validityPeriod.Validity.validityTimeSpecification.OverallPeriod.validPeriod{}.Period.recurringSpecialDay{}.PublicHoliday.specialDayType.xlink_href xml_buffer, condition.TimeCondition.validityPeriod.Validity.validityTimeSpecification.OverallPeriod.validPeriod{}.Period.recurringSpecialDay{}.PublicHoliday.specialDayType.xlink_role xml_buffer, condition.TimeCondition.validityPeriod.Validity.validityTimeSpecification.OverallPeriod.validPeriod{}.Period.recurringSpecialDay{}.PublicHoliday.specialDayType.xlink_title xml_buffer, condition.TimeCondition.validityPeriod.Validity.validityTimeSpecification.OverallPeriod.validPeriod{}.Period.recurringSpecialDay{}.PublicHoliday.publicEvent xml_buffer, condition.TimeCondition.validityPeriod.Validity.validityTimeSpecification.OverallPeriod.validPeriod{}.Period.recurringSpecialDay{}.PublicHoliday.publicHolidayName xml_buffer, condition.TimeCondition.validityPeriod.Validity.validityTimeSpecification.OverallPeriod.validPeriod{}.Period.recurringSpecialDay{}.SpecialDay.intersectWithApplicableDays xml_boolean, condition.TimeCondition.validityPeriod.Validity.validityTimeSpecification.OverallPeriod.validPeriod{}.Period.recurringSpecialDay{}.SpecialDay.specialDayType.owns xml_boolean, condition.TimeCondition.validityPeriod.Validity.validityTimeSpecification.OverallPeriod.validPeriod{}.Period.recurringSpecialDay{}.SpecialDay.specialDayType.nilReason xml_buffer, condition.TimeCondition.validityPeriod.Validity.validityTimeSpecification.OverallPeriod.validPeriod{}.Period.recurringSpecialDay{}.SpecialDay.specialDayType.gml_remoteSchema xml_buffer, condition.TimeCondition.validityPeriod.Validity.validityTimeSpecification.OverallPeriod.validPeriod{}.Period.recurringSpecialDay{}.SpecialDay.specialDayType.xlink_href xml_buffer, condition.TimeCondition.validityPeriod.Validity.validityTimeSpecification.OverallPeriod.validPeriod{}.Period.recurringSpecialDay{}.SpecialDay.specialDayType.xlink_role xml_buffer, condition.TimeCondition.validityPeriod.Validity.validityTimeSpecification.OverallPeriod.validPeriod{}.Period.recurringSpecialDay{}.SpecialDay.specialDayType.xlink_title xml_buffer, condition.TimeCondition.validityPeriod.Validity.validityTimeSpecification.OverallPeriod.validPeriod{}.Period.recurringSpecialDay{}.SpecialDay.publicEvent xml_buffer, condition.TimeCondition.validityPeriod.Validity.validityTimeSpecification.OverallPeriod.exceptionPeriod{}.Period.startOfPeriod xml_datetime, condition.TimeCondition.validityPeriod.Validity.validityTimeSpecification.OverallPeriod.exceptionPeriod{}.Period.endOfPeriod xml_datetime, condition.TimeCondition.validityPeriod.Validity.validityTimeSpecification.OverallPeriod.exceptionPeriod{}.Period.periodName xml_buffer, condition.TimeCondition.validityPeriod.Validity.validityTimeSpecification.OverallPeriod.exceptionPeriod{}.Period.recurringDayWeekMonthPeriod{}.DayWeekMonth.applicableDay{} xml_char(9), condition.TimeCondition.validityPeriod.Validity.validityTimeSpecification.OverallPeriod.exceptionPeriod{}.Period.recurringDayWeekMonthPeriod{}.DayWeekMonth.applicableWeek{} xml_char(10), condition.TimeCondition.validityPeriod.Validity.validityTimeSpecification.OverallPeriod.exceptionPeriod{}.Period.recurringDayWeekMonthPeriod{}.DayWeekMonth.applicableMonth{} xml_char(9), condition.TimeCondition.validityPeriod.Validity.validityTimeSpecification.OverallPeriod.exceptionPeriod{}.Period.recurringFuzzyTimePeriod{}.FuzzyTimePeriod.beginOrDuration.owns xml_boolean,
      condition.TimeCondition.validityPeriod.Validity.validityTimeSpecification.OverallPeriod.exceptionPeriod{}.Period.recurringFuzzyTimePeriod{}.FuzzyTimePeriod.beginOrDuration.nilReason xml_buffer, condition.TimeCondition.validityPeriod.Validity.validityTimeSpecification.OverallPeriod.exceptionPeriod{}.Period.recurringFuzzyTimePeriod{}.FuzzyTimePeriod.beginOrDuration.gml_remoteSchema xml_buffer, condition.TimeCondition.validityPeriod.Validity.validityTimeSpecification.OverallPeriod.exceptionPeriod{}.Period.recurringFuzzyTimePeriod{}.FuzzyTimePeriod.beginOrDuration.xlink_href xml_buffer, condition.TimeCondition.validityPeriod.Validity.validityTimeSpecification.OverallPeriod.exceptionPeriod{}.Period.recurringFuzzyTimePeriod{}.FuzzyTimePeriod.beginOrDuration.xlink_role xml_buffer, condition.TimeCondition.validityPeriod.Validity.validityTimeSpecification.OverallPeriod.exceptionPeriod{}.Period.recurringFuzzyTimePeriod{}.FuzzyTimePeriod.beginOrDuration.xlink_title xml_buffer, condition.TimeCondition.validityPeriod.Validity.validityTimeSpecification.OverallPeriod.exceptionPeriod{}.Period.recurringFuzzyTimePeriod{}.FuzzyTimePeriod.endOrDuration.owns xml_boolean, condition.TimeCondition.validityPeriod.Validity.validityTimeSpecification.OverallPeriod.exceptionPeriod{}.Period.recurringFuzzyTimePeriod{}.FuzzyTimePeriod.endOrDuration.nilReason xml_buffer, condition.TimeCondition.validityPeriod.Validity.validityTimeSpecification.OverallPeriod.exceptionPeriod{}.Period.recurringFuzzyTimePeriod{}.FuzzyTimePeriod.endOrDuration.gml_remoteSchema xml_buffer, condition.TimeCondition.validityPeriod.Validity.validityTimeSpecification.OverallPeriod.exceptionPeriod{}.Period.recurringFuzzyTimePeriod{}.FuzzyTimePeriod.endOrDuration.xlink_href xml_buffer, condition.TimeCondition.validityPeriod.Validity.validityTimeSpecification.OverallPeriod.exceptionPeriod{}.Period.recurringFuzzyTimePeriod{}.FuzzyTimePeriod.endOrDuration.xlink_role xml_buffer, condition.TimeCondition.validityPeriod.Validity.validityTimeSpecification.OverallPeriod.exceptionPeriod{}.Period.recurringFuzzyTimePeriod{}.FuzzyTimePeriod.endOrDuration.xlink_title xml_buffer, condition.TimeCondition.validityPeriod.Validity.validityTimeSpecification.OverallPeriod.exceptionPeriod{}.Period.recurringTimePeriodOfDay{}.TimePeriodOfDay.startTimeOfPeriod xml_time, condition.TimeCondition.validityPeriod.Validity.validityTimeSpecification.OverallPeriod.exceptionPeriod{}.Period.recurringTimePeriodOfDay{}.TimePeriodOfDay.endTimeOfPeriod xml_time, condition.TimeCondition.validityPeriod.Validity.validityTimeSpecification.OverallPeriod.exceptionPeriod{}.Period.recurringSpecialDay{}.PublicHoliday.intersectWithApplicableDays xml_boolean, condition.TimeCondition.validityPeriod.Validity.validityTimeSpecification.OverallPeriod.exceptionPeriod{}.Period.recurringSpecialDay{}.PublicHoliday.specialDayType.owns xml_boolean, condition.TimeCondition.validityPeriod.Validity.validityTimeSpecification.OverallPeriod.exceptionPeriod{}.Period.recurringSpecialDay{}.PublicHoliday.specialDayType.nilReason xml_buffer, condition.TimeCondition.validityPeriod.Validity.validityTimeSpecification.OverallPeriod.exceptionPeriod{}.Period.recurringSpecialDay{}.PublicHoliday.specialDayType.gml_remoteSchema xml_buffer, condition.TimeCondition.validityPeriod.Validity.validityTimeSpecification.OverallPeriod.exceptionPeriod{}.Period.recurringSpecialDay{}.PublicHoliday.specialDayType.xlink_href xml_buffer, condition.TimeCondition.validityPeriod.Validity.validityTimeSpecification.OverallPeriod.exceptionPeriod{}.Period.recurringSpecialDay{}.PublicHoliday.specialDayType.xlink_role xml_buffer, condition.TimeCondition.validityPeriod.Validity.validityTimeSpecification.OverallPeriod.exceptionPeriod{}.Period.recurringSpecialDay{}.PublicHoliday.specialDayType.xlink_title xml_buffer, condition.TimeCondition.validityPeriod.Validity.validityTimeSpecification.OverallPeriod.exceptionPeriod{}.Period.recurringSpecialDay{}.PublicHoliday.publicEvent xml_buffer, condition.TimeCondition.validityPeriod.Validity.validityTimeSpecification.OverallPeriod.exceptionPeriod{}.Period.recurringSpecialDay{}.PublicHoliday.publicHolidayName xml_buffer, condition.TimeCondition.validityPeriod.Validity.validityTimeSpecification.OverallPeriod.exceptionPeriod{}.Period.recurringSpecialDay{}.SpecialDay.intersectWithApplicableDays xml_boolean, condition.TimeCondition.validityPeriod.Validity.validityTimeSpecification.OverallPeriod.exceptionPeriod{}.Period.recurringSpecialDay{}.SpecialDay.specialDayType.owns xml_boolean, condition.TimeCondition.validityPeriod.Validity.validityTimeSpecification.OverallPeriod.exceptionPeriod{}.Period.recurringSpecialDay{}.SpecialDay.specialDayType.nilReason xml_buffer, condition.TimeCondition.validityPeriod.Validity.validityTimeSpecification.OverallPeriod.exceptionPeriod{}.Period.recurringSpecialDay{}.SpecialDay.specialDayType.gml_remoteSchema xml_buffer, condition.TimeCondition.validityPeriod.Validity.validityTimeSpecification.OverallPeriod.exceptionPeriod{}.Period.recurringSpecialDay{}.SpecialDay.specialDayType.xlink_href xml_buffer, condition.TimeCondition.validityPeriod.Validity.validityTimeSpecification.OverallPeriod.exceptionPeriod{}.Period.recurringSpecialDay{}.SpecialDay.specialDayType.xlink_role xml_buffer, condition.TimeCondition.validityPeriod.Validity.validityTimeSpecification.OverallPeriod.exceptionPeriod{}.Period.recurringSpecialDay{}.SpecialDay.specialDayType.xlink_title xml_buffer, condition.TimeCondition.validityPeriod.Validity.validityTimeSpecification.OverallPeriod.exceptionPeriod{}.Period.recurringSpecialDay{}.SpecialDay.publicEvent xml_buffer,
      condition.VehicleCondition.negate xml_boolean, condition.VehicleCondition.vehicleCharacteristics.VehicleCharacteristics.fuelType{}.owns xml_boolean, condition.VehicleCondition.vehicleCharacteristics.VehicleCharacteristics.fuelType{}.nilReason xml_buffer, condition.VehicleCondition.vehicleCharacteristics.VehicleCharacteristics.fuelType{}.gml_remoteSchema xml_buffer, condition.VehicleCondition.vehicleCharacteristics.VehicleCharacteristics.fuelType{}.xlink_href xml_buffer, condition.VehicleCondition.vehicleCharacteristics.VehicleCharacteristics.fuelType{}.xlink_role xml_buffer, condition.VehicleCondition.vehicleCharacteristics.VehicleCharacteristics.fuelType{}.xlink_title xml_buffer, condition.VehicleCondition.vehicleCharacteristics.VehicleCharacteristics.loadType.owns xml_boolean, condition.VehicleCondition.vehicleCharacteristics.VehicleCharacteristics.loadType.nilReason xml_buffer, condition.VehicleCondition.vehicleCharacteristics.VehicleCharacteristics.loadType.gml_remoteSchema xml_buffer, condition.VehicleCondition.vehicleCharacteristics.VehicleCharacteristics.loadType.xlink_href xml_buffer, condition.VehicleCondition.vehicleCharacteristics.VehicleCharacteristics.loadType.xlink_role xml_buffer, condition.VehicleCondition.vehicleCharacteristics.VehicleCharacteristics.loadType.xlink_title xml_buffer, condition.VehicleCondition.vehicleCharacteristics.VehicleCharacteristics.vehicleEquipment.owns xml_boolean, condition.VehicleCondition.vehicleCharacteristics.VehicleCharacteristics.vehicleEquipment.nilReason xml_buffer, condition.VehicleCondition.vehicleCharacteristics.VehicleCharacteristics.vehicleEquipment.gml_remoteSchema xml_buffer, condition.VehicleCondition.vehicleCharacteristics.VehicleCharacteristics.vehicleEquipment.xlink_href xml_buffer, condition.VehicleCondition.vehicleCharacteristics.VehicleCharacteristics.vehicleEquipment.xlink_role xml_buffer, condition.VehicleCondition.vehicleCharacteristics.VehicleCharacteristics.vehicleEquipment.xlink_title xml_buffer, condition.VehicleCondition.vehicleCharacteristics.VehicleCharacteristics.vehicleType{}.owns xml_boolean, condition.VehicleCondition.vehicleCharacteristics.VehicleCharacteristics.vehicleType{}.nilReason xml_buffer, condition.VehicleCondition.vehicleCharacteristics.VehicleCharacteristics.vehicleType{}.gml_remoteSchema xml_buffer, condition.VehicleCondition.vehicleCharacteristics.VehicleCharacteristics.vehicleType{}.xlink_href xml_buffer, condition.VehicleCondition.vehicleCharacteristics.VehicleCharacteristics.vehicleType{}.xlink_role xml_buffer, condition.VehicleCondition.vehicleCharacteristics.VehicleCharacteristics.vehicleType{}.xlink_title xml_buffer, condition.VehicleCondition.vehicleCharacteristics.VehicleCharacteristics.vehicleUsage.owns xml_boolean, condition.VehicleCondition.vehicleCharacteristics.VehicleCharacteristics.vehicleUsage.nilReason xml_buffer, condition.VehicleCondition.vehicleCharacteristics.VehicleCharacteristics.vehicleUsage.gml_remoteSchema xml_buffer, condition.VehicleCondition.vehicleCharacteristics.VehicleCharacteristics.vehicleUsage.xlink_href xml_buffer, condition.VehicleCondition.vehicleCharacteristics.VehicleCharacteristics.vehicleUsage.xlink_role xml_buffer,
      condition.VehicleCondition.vehicleCharacteristics.VehicleCharacteristics.vehicleUsage.xlink_title xml_buffer, condition.VehicleCondition.vehicleCharacteristics.VehicleCharacteristics.yearOfFirstRegistration xml_int64, condition.VehicleCondition.vehicleCharacteristics.VehicleCharacteristics.heightCharacteristic{}.HeightCharacteristic.comparisonOperator xml_char(20), condition.VehicleCondition.vehicleCharacteristics.VehicleCharacteristics.heightCharacteristic{}.HeightCharacteristic.vehicleHeight xml_real64, condition.VehicleCondition.vehicleCharacteristics.VehicleCharacteristics.heightCharacteristic{}.HeightCharacteristic.vehicleHeight.uom xml_buffer, condition.VehicleCondition.vehicleCharacteristics.VehicleCharacteristics.widthCharacteristic{}.WidthCharacteristic.comparisonOperator xml_char(20), condition.VehicleCondition.vehicleCharacteristics.VehicleCharacteristics.widthCharacteristic{}.WidthCharacteristic.vehicleWidth xml_real64, condition.VehicleCondition.vehicleCharacteristics.VehicleCharacteristics.widthCharacteristic{}.WidthCharacteristic.vehicleWidth.uom xml_buffer, condition.VehicleCondition.vehicleCharacteristics.VehicleCharacteristics.heaviestAxleWeightCharacteristic{}.HeaviestAxleWeightCharacteristic.comparisonOperator xml_char(20), condition.VehicleCondition.vehicleCharacteristics.VehicleCharacteristics.heaviestAxleWeightCharacteristic{}.HeaviestAxleWeightCharacteristic.heaviestAxleWeight xml_real64, condition.VehicleCondition.vehicleCharacteristics.VehicleCharacteristics.heaviestAxleWeightCharacteristic{}.HeaviestAxleWeightCharacteristic.heaviestAxleWeight.uom xml_buffer, condition.VehicleCondition.vehicleCharacteristics.VehicleCharacteristics.grossWeightCharacteristic{}.GrossWeightCharacteristic.comparisonOperator xml_char(20), condition.VehicleCondition.vehicleCharacteristics.VehicleCharacteristics.grossWeightCharacteristic{}.GrossWeightCharacteristic.grossVehicleWeight xml_real64, condition.VehicleCondition.vehicleCharacteristics.VehicleCharacteristics.grossWeightCharacteristic{}.GrossWeightCharacteristic.grossVehicleWeight.uom xml_buffer, condition.VehicleCondition.vehicleCharacteristics.VehicleCharacteristics.grossWeightCharacteristic{}.GrossWeightCharacteristic.typeOfWeight.owns xml_boolean, condition.VehicleCondition.vehicleCharacteristics.VehicleCharacteristics.grossWeightCharacteristic{}.GrossWeightCharacteristic.typeOfWeight.nilReason xml_buffer, condition.VehicleCondition.vehicleCharacteristics.VehicleCharacteristics.grossWeightCharacteristic{}.GrossWeightCharacteristic.typeOfWeight.gml_remoteSchema xml_buffer, condition.VehicleCondition.vehicleCharacteristics.VehicleCharacteristics.grossWeightCharacteristic{}.GrossWeightCharacteristic.typeOfWeight.xlink_href xml_buffer, condition.VehicleCondition.vehicleCharacteristics.VehicleCharacteristics.grossWeightCharacteristic{}.GrossWeightCharacteristic.typeOfWeight.xlink_role xml_buffer, condition.VehicleCondition.vehicleCharacteristics.VehicleCharacteristics.grossWeightCharacteristic{}.GrossWeightCharacteristic.typeOfWeight.xlink_title xml_buffer, condition.VehicleCondition.vehicleCharacteristics.VehicleCharacteristics.numberOfAxlesCharacteristic{}.NumberOfAxlesCharacteristic.comparisonOperator xml_char(20), condition.VehicleCondition.vehicleCharacteristics.VehicleCharacteristics.numberOfAxlesCharacteristic{}.NumberOfAxlesCharacteristic.numberOfAxles xml_int64, condition.VehicleCondition.vehicleCharacteristics.VehicleCharacteristics.emissions{}.Emissions.emissionClassificationEuro.owns xml_boolean, condition.VehicleCondition.vehicleCharacteristics.VehicleCharacteristics.emissions{}.Emissions.emissionClassificationEuro.nilReason xml_buffer, condition.VehicleCondition.vehicleCharacteristics.VehicleCharacteristics.emissions{}.Emissions.emissionClassificationEuro.gml_remoteSchema xml_buffer, condition.VehicleCondition.vehicleCharacteristics.VehicleCharacteristics.emissions{}.Emissions.emissionClassificationEuro.xlink_href xml_buffer, condition.VehicleCondition.vehicleCharacteristics.VehicleCharacteristics.emissions{}.Emissions.emissionClassificationEuro.xlink_role xml_buffer, condition.VehicleCondition.vehicleCharacteristics.VehicleCharacteristics.emissions{}.Emissions.emissionClassificationEuro.xlink_title xml_buffer, condition.VehicleCondition.vehicleCharacteristics.VehicleCharacteristics.emissions{}.Emissions.emissionClassificationOther{} xml_buffer, condition.VehicleCondition.vehicleCharacteristics.VehicleCharacteristics.emissions{}.Emissions.emissionLevel.owns xml_boolean,
      condition.VehicleCondition.vehicleCharacteristics.VehicleCharacteristics.emissions{}.Emissions.emissionLevel.nilReason xml_buffer, condition.VehicleCondition.vehicleCharacteristics.VehicleCharacteristics.emissions{}.Emissions.emissionLevel.gml_remoteSchema xml_buffer, condition.VehicleCondition.vehicleCharacteristics.VehicleCharacteristics.emissions{}.Emissions.emissionLevel.xlink_href xml_buffer, condition.VehicleCondition.vehicleCharacteristics.VehicleCharacteristics.emissions{}.Emissions.emissionLevel.xlink_role xml_buffer, condition.VehicleCondition.vehicleCharacteristics.VehicleCharacteristics.emissions{}.Emissions.emissionLevel.xlink_title xml_buffer, condition.VehicleCondition.vehicleCharacteristics.VehicleCharacteristics.lengthCharacteristic{}.LengthCharacteristic.comparisonOperator xml_char(20), condition.VehicleCondition.vehicleCharacteristics.VehicleCharacteristics.lengthCharacteristic{}.LengthCharacteristic.vehicleLength xml_real64, condition.VehicleCondition.vehicleCharacteristics.VehicleCharacteristics.lengthCharacteristic{}.LengthCharacteristic.vehicleLength.uom xml_buffer, condition.WeatherCondition.negate xml_boolean, condition.WeatherCondition.weatherType.owns xml_boolean, condition.WeatherCondition.weatherType.nilReason xml_buffer, condition.WeatherCondition.weatherType.gml_remoteSchema xml_buffer, condition.WeatherCondition.weatherType.xlink_href xml_buffer, condition.WeatherCondition.weatherType.xlink_role xml_buffer, condition.WeatherCondition.weatherType.xlink_title xml_buffer, locationReference{} xml_xml, locationReference{}.GeometryLocationReference.encodedGeometry.LineString.posList xml_char(461), locationReference{}.GeometryLocationReference.encodedGeometry.LineString.srsDimension xml_decimal(2,0), locationReference{}.GeometryLocationReference.encodedGeometry.LineString.srsName xml_char(10), locationReference{}.GeometryLocationReference.encodedGeometry.Point.pos xml_char(38), locationReference{}.GeometryLocationReference.encodedGeometry.Point.srsDimension xml_decimal(2,0), locationReference{}.GeometryLocationReference.encodedGeometry.Point.srsName xml_char(10), locationReference{}.OpenLRLocationReference.binaryLocationReference.BinaryLocationReference.base64String xml_char(25), locationReference{}.OpenLRLocationReference.binaryLocationReference.BinaryLocationReference.openLRBinaryVersion xml_char(1), locationReference{}.OpenLRLocationReference.binaryLocationReference.BinaryLocationReference.openLRBinaryVersion.href xml_char(61), properties{}.GenericRoadFeatureProperty.value{}.measure xml_decimal(2,0), properties{}.GenericRoadFeatureProperty.value{}.measure.uom xml_char(4)
    -> ListSearcher [off]
    -> RoadFeature_RDS
ListSearcher
    ATTR_VALUE = encodedGeometry
    INDEX_ATTR = _list_index
    LIST_ATTR = locationReference{}
    MATCHTYPE = REGULAR_EXPRESSION_ENCODED
    FOUND -> ListIndexer
ListIndexer
    INDEX = @Value(_list_index)
    LIST_ATTR = locationReference{}
    -> GeometryReplacer
GeometryReplacer
    KIND_LONG = GML
    REMOVE_ATTRIBUTE = Yes
    SOURCE = @Value(locationReference)
    SRS_AXIS_ORDER_DISPLAY = 1,2
    -> RoadFeature
RoadFeature: Inspector
RoadFeature_RDS: Inspector
