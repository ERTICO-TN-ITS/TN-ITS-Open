FME workspace Excel2Codelists.fmw

Parameters:
- DestDataset_TEXTLINE =
- DestDataset_TEXTLINE_4 =
- DestDataset_TEXTLINE_5 =
- SourceDataset_XLSXR =
- SourceDataset_XLSXR_3 =
- owlURI =

Readers:
- XLSXR_1: XLSXR from $(SourceDataset_XLSXR)
- XLSXR_2: XLSXR from $(SourceDataset_XLSXR_3)

Writers:
- TEXTLINE_1: TEXTLINE to $(DestDataset_TEXTLINE)
- TEXTLINE_2: TEXTLINE to $(DestDataset_TEXTLINE_5)
- TEXTLINE_3: TEXTLINE to $(DestDataset_TEXTLINE_4)

Codelists (reader XLSXR_1)
    attributes: Element char(27), Attribute string, Definition char(461)
    -> AttributeManager_6
AttributeManager_6
    ATTR_TABLE:
      SET_TO Element = @ReplaceString(@Trim(@Value(Element)),"Code","")Code
      RENAME_SET_VALUE Definition > cl_description
    -> DateTimeStamper
DateTimeStamper
    DATETIME_ATTR = _timestamp
    STAMP_TYPE = date
    TIMEZONE = local
    -> FeatureMerger [SUPPLIER]
WeightTypeCode (reader XLSXR_2)
    attributes: identifier char(17), description char(57), C string, The type of traffic sign according to separate codelist (see TrafficSignType) char(78), D string, E string
    -> TestFilter
TestFilter
    DEFAULT_VALUE = <UNFILTERED>
    TEST_LIST = BOOL_OP,OR,COMPOSITE_TEST,<Unused>,TEST_CLAUSE,"TEST @Value(identifier) ATTRIBUTE_HAS_VALUE """"",identifier ATTRIBUTE_HAS_VALUE
    identifier ATTRIBUTE_HAS_VALUE -> FeatureMerger [REQUESTOR]
FeatureMerger
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(fme_feature_type) @Value(Element) AUTO
    MERGE_TYPE = Attributes Only
    PROCESS_DUPS = Yes
    REJECT_NULL_MISSING_KEYS = No
    SUPPLIERS_FIRST = No
    MERGED -> AttributeExposer
    MERGED -> StringReplacer_2
    UNMERGED_REQUESTOR -> FeatureMerger_UnmergedRequestor
    UNUSED_SUPPLIER -> FeatureMerger_UnusedSupplier
    <REJECTED> -> FeatureMerger__Rejected_
FeatureMerger_UnmergedRequestor: Inspector
FeatureMerger_UnusedSupplier: Inspector
FeatureMerger__Rejected_: Inspector

Bookmark: RDF (Turtle)
StringReplacer_2
    CASE = yes
    FIND_TEXT = Code$
    NO_MATCH = _FME_NO_OP_
    REGEXP = YES
    SRC_ATTRS = fme_feature_type
    -> StringReplacer
StringReplacer
    CASE = YES
    FIND_TEXT = \n
    NO_MATCH = _FME_NO_OP_
    REGEXP = YES
    REPLACE_TEXT = " "
    SRC_ATTRS = description
    -> StringReplacer_5
StringReplacer_5
    CASE = YES
    FIND_TEXT = "
    NO_MATCH = _FME_NO_OP_
    REGEXP = NO
    REPLACE_TEXT = \"
    SRC_ATTRS = description
    -> AttributeManager
AttributeManager
    ATTR_TABLE:
      SET_TO individual = :@Value(fme_feature_type).@Value(identifier) a :@Value(fme_feature_type), skos:Concept  ;
                 skos:inScheme :@Value(fme_feature_type)Code ;
                 rdfs:label "@Value(identifier)"@en ;
                 skos:definition "@Value(description)"@en .
    -> ListBuilder_2
AttributeManager_7
    ATTR_TABLE:
      SET_TO cl_ttl =
        :@Value(Element) a skos:ConceptScheme ;
            dc:isFormatOf :@Value(fme_feature_type) ;
            	skos:definition "@Value(cl_description)" .


        @Value(_concatenated)
    -> ListBuilder_3
ListBuilder_3
    GROUP_BY = _timestamp
    LIST_ATTRS_TO_INCLUDE = cl_ttl
    LIST_NAME = _list
    -> ListConcatenator_2
ListConcatenator_2
    DROP_EMPTY_PARTS = No
    LIST_ATTR = _list{}.cl_ttl
    VAL_ATTR = _concatenated
    -> AttributeManager_3

Bookmark: Individual files
ListBuilder_2
    GROUP_BY = Element cl_description _timestamp fme_feature_type
    LIST_ATTRS_TO_INCLUDE = description identifier individual
    LIST_NAME = _list
    -> ListConcatenator
ListConcatenator
    DROP_EMPTY_PARTS = No
    LIST_ATTR = _list{}.individual
    VAL_ATTR = _concatenated
    -> AttributeManager_2
    -> AttributeManager_7
AttributeManager_2
    ATTR_TABLE:
      SET_TO text_line_data = @prefix : <$(owlURI)#> .
        @prefix dc: <http://purl.org/dc/elements/1.1/> .
        @prefix owl: <http://www.w3.org/2002/07/owl#> .
        @prefix rdf: <http://www.w3.org/1999/02/22-rdf-syntax-ns#> .
        @prefix xml: <http://www.w3.org/XML/1998/namespace> .
        @prefix xsd: <http://www.w3.org/2001/XMLSchema#> .
        @prefix rdfs: <http://www.w3.org/2000/01/rdf-schema#> .
        @prefix skos: <http://www.w3.org/2004/02/skos/core#> .
        @prefix tnits: <$(owlURI)#> .
        @prefix dcterms: <http://purl.org/dc/terms/> .
        @base <$(owlURI)> .

        <$(owlURI)/codes> a owl:Ontology ;
        	owl:imports <http://www.w3.org/2004/02/skos/core> ;
        	dc:creator "TN-ITS" ;
        	dc:date "@Value(_timestamp)" ;
        	dc:description "Code list values for TN-ITS code lists"@en ;
        	dcterms:title "TN-ITS @Value(Element)"@en.

        :@Value(Element) a skos:ConceptScheme ;
            dc:isFormatOf :@Value(fme_feature_type) ;
            	skos:definition "@Value(cl_description)" .


        @Value(_concatenated)
    -> text_line (writer TEXTLINE_2) [off]
text_line (writer TEXTLINE_2) [off]
    attributes: text_line_data buffer

Bookmark: One file
AttributeManager_3
    ATTR_TABLE:
      SET_TO text_line_data = @prefix : <$(owlURI)#> .
        @prefix dc: <http://purl.org/dc/elements/1.1/> .
        @prefix owl: <http://www.w3.org/2002/07/owl#> .
        @prefix rdf: <http://www.w3.org/1999/02/22-rdf-syntax-ns#> .
        @prefix xml: <http://www.w3.org/XML/1998/namespace> .
        @prefix xsd: <http://www.w3.org/2001/XMLSchema#> .
        @prefix rdfs: <http://www.w3.org/2000/01/rdf-schema#> .
        @prefix skos: <http://www.w3.org/2004/02/skos/core#> .
        @prefix tnits: <$(owlURI)#> .
        @prefix dcterms: <http://purl.org/dc/terms/> .
        @base <$(owlURI)> .

        <$(owlURI)/codes> a owl:Ontology ;
        	owl:imports <http://www.w3.org/2004/02/skos/core> ;
        	dc:creator "TN-ITS" ;
        	dc:date "@Value(_timestamp)" ;
        	dc:description "Code list values for TN-ITS code lists"@en ;
        	dcterms:title "TN-ITS Codes"@en.


        @Value(_concatenated)
    -> text_line (writer TEXTLINE_3)
text_line (writer TEXTLINE_3)
    attributes: text_line_data buffer

Bookmark: GML Dictionary
AttributeExposer
    ATTR_LIST = gmlid
    -> AttributeManager_4
AttributeManager_4
    ATTR_TABLE:
      SET_TO fme_feature_type = @Value(Element)
      SET_TO identifier = FME_CONDITIONAL:DEFAULT_VALUE'_FME_NO_OP_'BOOL_OP;OR;COMPOSITE_TEST;<Unused>;TEST @Value(fme_feature_type) = RoadSignTypeCode'@ReplaceString(@Value(identifier),-,_)'FME_NUM_CONDITIONS2___
      SET_TO gmlid = FME_CONDITIONAL:DEFAULT_VALUE'@Value(identifier)'BOOL_OP;OR;COMPOSITE_TEST;<Unused>;TEST @Value(fme_feature_type) = RoadSignTypeCode'gdd@Value(identifier)'FME_NUM_CONDITIONS2___
      SET_TO xml = 	<gml:dictionaryEntry>
        		<gml:Definition gml:id="@Value(gmlid)">
        			<gml:description>@Value(description)</gml:description>
        			<gml:identifier codeSpace="http://spec.tn-its.eu/codelists/@Value(fme_feature_type)">@Value(identifier)</gml:identifier>
        		</gml:Definition>
        	</gml:dictionaryEntry>
    -> ListBuilder
ListBuilder
    GROUPS_ORDERED = No
    GROUP_BY = cl_description fme_feature_type
    LIST_ATTRS_TO_INCLUDE = xml
    LIST_NAME = _list
    -> XMLTemplater [ROOT]
XMLTemplater
    OUTPUT_XML_HEADER = Yes
    RESULT_ATTRIBUTE = _result
    ROOT_QUERY_EXPR:
      <?xml version="1.0" encoding="UTF-8"?>
      <gml:Dictionary gml:id="WarningSignTypeCode" xmlns:gml="http://www.opengis.net/gml/3.2"
      	xmlns:gco="http://www.isotc211.org/2005/gco" xmlns:gmd="http://www.isotc211.org/2005/gmd"
      	xmlns:gsr="http://www.isotc211.org/2005/gsr" xmlns:gss="http://www.isotc211.org/2005/gss"
      	xmlns:gts="http://www.isotc211.org/2005/gts" xmlns:xlink="http://www.w3.org/1999/xlink"
      	xmlns:xsi="http://www.w3.org/2001/XMLSchema-instance"
      	xsi:schemaLocation="http://www.opengis.net/gml/3.2
      http://schemas.opengis.net/gml/3.2.1/gml.xsd">
      	<gml:description>{fme:get-attribute("cl_description")}</gml:description>
      	<gml:identifier codeSpace="http://spec.tn-its.eu/codelists/">{fme:get-attribute("fme_feature_type")}</gml:identifier>
      {fme:get-list-attribute("_list{}.xml")}
      </gml:Dictionary>
    VISIBLE_QUERY_VALIDATE = No
    -> StringReplacer_3
StringReplacer_3
    CASE = NO
    FIND_TEXT = &lt;
    NO_MATCH = _FME_NO_OP_
    REGEXP = NO
    REPLACE_TEXT = <
    SRC_ATTRS = _result
    -> StringReplacer_4
StringReplacer_4
    CASE = NO
    FIND_TEXT = &gt;
    NO_MATCH = _FME_NO_OP_
    REGEXP = NO
    REPLACE_TEXT = >
    SRC_ATTRS = _result
    -> XMLFormatter
XMLFormatter
    COLLAPSE_EMPTY_ELEMENT = No
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = No
    REPLACE_TABS_WITH_SPACES = no
    SCHEMALOC_CLEANUP = No
    TEXT_INDENT = no
    WHITESPACE_HANDLING = Preserve all whitespace
    XML_ATTR_TEXT = _result
    XML_INPUT_TYPE = Attribute Specifying XML Text
    XML_OUTPUT_ATTR = _xml_output
    XML_OUTPUT_TYPE = Attribute
    PASSED -> AttributeManager_5
AttributeManager_5
    ATTR_TABLE = RENAME_SET_VALUE _result > text_line_data
    -> text_line (writer TEXTLINE_1)
    -> AttributeManager_5_Output
text_line (writer TEXTLINE_1) [off]
    attributes: text_line_data buffer
AttributeManager_5_Output: Inspector [off]
    TACKATTRS = fme_feature_type
